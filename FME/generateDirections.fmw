FME workspace generateDirections.fmw

Parameters:
- SourceDataset_SHAPE = C:\AndrewRoss\Work\AR_BusRouteDirections\Input\Routes.shp   # Source ESRI Shape File(s)
- SourceDataset_SHAPE_5 = C:\AndrewRoss\Basedata\Transportation\DRA\Roads.shp   # Source ESRI Shape File(s)
- SourceDataset_SHAPE_7 = C:\AndrewRoss\Basedata\Transit\Stops\BusStops.shp   # Source ESRI Shape File(s)
- DestDataset_CSV = C:\AndrewRoss\Work\AR_BusRouteDirections\Output   # Destination Comma Separated Value (CSV) Directory
- SourceDataset_SHAPE_6 = C:\AndrewRoss\Basedata\Transportation\DRA\RoadsKamloops_20130118.shp   # Source ESRI Shape File(s)

Readers:
- SHAPE_1: SHAPE from $(SourceDataset_SHAPE)
- SHAPE_2: SHAPE from $(SourceDataset_SHAPE_5)
- SHAPE_3: SHAPE from $(SourceDataset_SHAPE_7)
- SHAPE_4: SHAPE from $(SourceDataset_SHAPE_6)

Writers:
- CSV_1: CSV to $(DestDataset_CSV)

Routes (reader SHAPE_1)
    attributes: ROUTEID char(5), PATTERNID char(20), PATTERNID2 number(4,0), DIRECTION char(20), GROUP char(8), HIERARCHY number(1,0), WCHEND number(2,0), LENGTH number(8,1), PTRNCNT number(5,0), DISTANCE number(8,1), SEGSEQ number(3,0), GLOBALRANK number(4,0), INDIVLINE number(1,0), ENDOFPATH number(1,0), ID number(8,0), NAV_DIR char(3), SNIPFROM number(4,1), SNIPTO number(4,1), STOPIDF number(8,0), STOPIDT number(8,0)
    -> AttributeRenamer
AttributeRenamer
    ATTR_LIST = STOPIDT,END_STOPID,"",STOPIDF,START_STOPID,"",ROUTEID,ROUTENUM,"",PATTERNID2,PTRNNUM,"",SEGSEQ,ORDR,"",WCHEND,SIDE,""
    -> AttributeCreator
AttributeCreator
    ATTR_LIST = ROUTENAME,myRoute,BCTSYSTEM,my BCT system,BCTREGION,my BCT region
    -> Tester_2
    -> Tester
Note: Filter Route: 17 / Pattern: 200, 201
Tester
    TEST_DESCRIPTION = ""
    TEST_CLAUSE:
      TEST "@Value(ROUTENUM)" NOT_= "17"
      TEST "@Value(PTRNNUM)" NOT_IN "(200, 201)"
    BOOL_OP = AND
    TEST_MODE = Automatic
    PASSED -> generateDrivingDirections [input 1]
Tester_2 [off]
    TEST_DESCRIPTION = ""
    TEST_CLAUSE:
      TEST "@Value(ROUTENUM)" = "7"
      TEST "@Value(PTRNNUM)" = "100"
    BOOL_OP = AND
    TEST_MODE = Automatic
    PASSED -> generateDrivingDirections [input 1]
RoadsKamloops_20130118 (reader SHAPE_4)
    attributes: ID number(8,0), NAME_FULL char(70), NAME_ID number(8,0), FROM_LEFT number(8,0), TO_LEFT number(8,0), FROM_RIGHT number(8,0), TO_RIGHT number(8,0), SINGLE_ADD number(8,0), PARITY_LFT char(1), PARITY_RGT char(1), CITY_LEFT char(50), CITY_RIGHT char(50), RD_CLASS char(12), NAME_BASE char(50), NAME_PREF char(2), NAME_PRTYP char(12), NAME_STRUC char(12), NAME_SUFF char(2), NAV_DIR char(1), RD_DIVIDED char(4)
    -> generateDrivingDirections [input 2]
Roads (reader SHAPE_2) [off]
    attributes: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
BusStops (reader SHAPE_3)
    attributes: STOPID number(7,0), STOPNAME char(75), STOPCLASS number(2,0), LATITUDE number(15,10), LONGITUDE number(15,10), STATUS char(14), BCTREGION char(35), REGDIST char(35), BCTSYSTEM char(35), EXCHANGE char(35), PARKNRIDE char(35), AREANAME char(35), ADDNUMBER number(6,0), ADDSTREET char(35), ADDCITY char(35), STOPOWNER char(35), STOPRESP char(1), SBOWNER char(35), SBRESP char(35), BSSIGNAGE number(2,0), STOPIDDIS number(2,0), SIGNPOST number(2,0), SCHEDHOLD number(2,0), RTID number(2,0), BENCH number(2,0), SHELTER number(2,0), MAPDISPLAY number(2,0), ADVERT number(2,0), GARBAGEBIN number(2,0), HEATING number(2,0),
      LIGHTING number(2,0), SHADE number(2,0), ACCESSIBLE number(2,0), SURFACE number(2,0), CSD number(2,0), CURBHEIGHT number(3,0), CPLA number(2,0), TGSI number(2,0), SIDEWALK number(2,0), COMMENTS char(254), MODDATE date
    -> generateDrivingDirections [input 3]
generateDrivingDirections
    -> DIRECTIONS (writer CSV_1)
DIRECTIONS (writer CSV_1)
    attributes: ROUTEID char(20), PTRNNUM char(20), DIRECTIONS char(20)
